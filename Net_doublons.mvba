Attribute VB_Name = "CMoteurScan"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

' =============================================================================
' CMoteurScan - Orchestration du scan et detection des doublons
' Connait l'API MicroStation (scan, suppression)
' Delegue le calcul de signature aux classes CSignatureXxx
' =============================================================================

' --- Classes metier ---
Private m_oSigLigne     As CSignatureLigne
Private m_oSigTexte     As CSignatureTexte
Private m_oSigArc       As CSignatureArc
Private m_oSigCourbe    As CSignatureCourbe
Private m_oSigForme     As CSignatureForme
Private m_oSigCell      As CSignatureCell

' --- Resultats ---
Private m_lNbScannes    As Long
Private m_lNbTraites    As Long
Private m_lNbIgnores    As Long
Private m_lNbDoublons   As Long
Private m_lNbSupprimes  As Long
Private m_aDoublons()   As DLong
Private m_lCountDoub    As Long

' --- Surbrillance ---
Private m_bSurbrillance As Boolean

' --- Dictionnaire des signatures ---
Private m_dictSigs      As Object

' --- Proprietes en lecture ---
Public Property Get NbElementsScannes() As Long
    NbElementsScannes = m_lNbScannes
End Property

Public Property Get NbDoublonsTrouves() As Long
    NbDoublonsTrouves = m_lNbDoublons
End Property

Public Property Get NbSupprimes() As Long
    NbSupprimes = m_lNbSupprimes
End Property

' Elements scannes dont la signature etait vide (type non gere ou erreur
' d'extraction avalee) : exclus de la detection. Utile au diagnostic.
Public Property Get NbIgnores() As Long
    NbIgnores = m_lNbIgnores
End Property

' --- Initialisation des classes de signature ---
Private Sub InitSignateurs(ByVal oSettings As CSettings)
    Set m_oSigLigne = New CSignatureLigne
    m_oSigLigne.Init oSettings.dTolerance

    Set m_oSigTexte = New CSignatureTexte
    m_oSigTexte.Init oSettings.dTolerance

    Set m_oSigArc = New CSignatureArc
    m_oSigArc.Init oSettings.dTolerance

    Set m_oSigCourbe = New CSignatureCourbe
    m_oSigCourbe.Init oSettings.dTolerance

    Set m_oSigForme = New CSignatureForme
    m_oSigForme.Init oSettings.dTolerance

    Set m_oSigCell = New CSignatureCell
    m_oSigCell.Init oSettings.dTolerance
End Sub

' =============================================================================
' Analyser - Scanne le modele et identifie les doublons
' =============================================================================
Sub Analyser(ByVal oModel As ModelReference, ByVal oSettings As CSettings)
    Dim oScanCriteria As ElementScanCriteria
    Dim oEnum As ElementEnumerator
    Dim oElement As Element
    Dim sSig As String

    InitSignateurs oSettings

    If Not m_dictSigs Is Nothing Then Set m_dictSigs = Nothing
    Set m_dictSigs = CreateObject("Scripting.Dictionary")
    m_dictSigs.CompareMode = vbBinaryCompare

    m_lNbScannes = 0
    m_lNbTraites = 0
    m_lNbIgnores = 0
    m_lNbDoublons = 0
    m_lNbSupprimes = 0
    m_lCountDoub = 0
    Erase m_aDoublons
    ReDim m_aDoublons(0)

    Set oScanCriteria = New ElementScanCriteria
    oScanCriteria.ExcludeAllTypes
    ConfigurerCriteres oScanCriteria, oSettings

    ShowCommand "Nettoyage Doublons"
    ShowPrompt "Analyse en cours..."

    Set oEnum = oModel.Scan(oScanCriteria)

    Do While oEnum.MoveNext
        Set oElement = oEnum.Current
        m_lNbScannes = m_lNbScannes + 1

        If Not oElement.IsComponentElement Then
            sSig = GenererSignature(oElement, oSettings)

            If Len(sSig) > 0 Then
                m_lNbTraites = m_lNbTraites + 1

                If m_dictSigs.Exists(sSig) Then
                    m_lNbDoublons = m_lNbDoublons + 1
                    m_lCountDoub = m_lCountDoub + 1
                    ReDim Preserve m_aDoublons(m_lCountDoub - 1)
                    m_aDoublons(m_lCountDoub - 1) = oElement.ID
                Else
                    m_dictSigs.Add sSig, oElement.ID
                End If
            Else
                ' Signature vide : type non gere ou erreur d'extraction avalee
                ' par le On Error de SignatureGeometrique -> element ignore.
                m_lNbIgnores = m_lNbIgnores + 1
            End If
        End If

        If m_lNbScannes Mod 1000 = 0 Then
            ShowPrompt "Analyse: " & m_lNbScannes & " scannes, " & _
                       m_lNbDoublons & " doublons..."
            DoEvents
        End If
    Loop

    ShowPrompt "Analyse terminee: " & m_lNbDoublons & " doublons sur " & _
               m_lNbScannes & " elements (" & m_lNbIgnores & " ignores)."
End Sub

' =============================================================================
' SupprimerDoublons - Supprime les elements identifies comme doublons
' =============================================================================
Sub SupprimerDoublons(ByVal oModel As ModelReference)
    Dim i As Long
    Dim oElem As Element

    m_lNbSupprimes = 0
    ShowPrompt "Suppression en cours..."

    For i = 0 To m_lCountDoub - 1
        On Error Resume Next
        Set oElem = Nothing
        Set oElem = oModel.GetElementByID(m_aDoublons(i))
        If Not oElem Is Nothing Then
            oModel.RemoveElement oElem
            m_lNbSupprimes = m_lNbSupprimes + 1
        End If
        On Error GoTo 0

        If m_lNbSupprimes Mod 100 = 0 And m_lNbSupprimes > 0 Then
            ShowPrompt "Suppression: " & m_lNbSupprimes & " / " & m_lNbDoublons
            DoEvents
        End If
    Next i

    CommandState.StartDefaultCommand
    ShowPrompt "Termine: " & m_lNbSupprimes & " doublons supprimes."
End Sub

' =============================================================================
' SurlignierDoublons - Selectionne les doublons (selection set)
' =============================================================================
Sub SurlignierDoublons(ByVal oModel As ModelReference)
    Dim i As Long
    Dim oElem As Element

    If m_lCountDoub = 0 Then Exit Sub

    oModel.UnselectAllElements

    For i = 0 To m_lCountDoub - 1
        On Error Resume Next
        Set oElem = Nothing
        Set oElem = oModel.GetElementByID(m_aDoublons(i))
        If Not oElem Is Nothing Then
            oModel.SelectElement oElem
        End If
        On Error GoTo 0
    Next i

    m_bSurbrillance = True
End Sub

' =============================================================================
' EffacerSurbrillance - Deselectionne tous les elements
' =============================================================================
Sub EffacerSurbrillance(ByVal oModel As ModelReference)
    If Not m_bSurbrillance Then Exit Sub
    oModel.UnselectAllElements
    m_bSurbrillance = False
End Sub

' =============================================================================
' Configuration des criteres de scan selon les options
' =============================================================================
Private Sub ConfigurerCriteres(ByVal oSC As ElementScanCriteria, _
                               ByVal oSettings As CSettings)
    If oSettings.bLignes Then
        oSC.IncludeType msdElementTypeLine
        oSC.IncludeType msdElementTypeLineString
        oSC.IncludeType msdElementTypePointString
    End If
    If oSettings.bTextes Then
        oSC.IncludeType msdElementTypeText
        oSC.IncludeType msdElementTypeTextNode
    End If
    If oSettings.bArcs Then
        oSC.IncludeType msdElementTypeArc
        oSC.IncludeType msdElementTypeEllipse
    End If
    If oSettings.bCourbes Then
        oSC.IncludeType msdElementTypeCurve
        oSC.IncludeType msdElementTypeBsplineCurve
        oSC.IncludeType msdElementTypeBsplineSurface
    End If
    If oSettings.bFormes Then
        oSC.IncludeType msdElementTypeShape
        oSC.IncludeType msdElementTypeComplexString
        oSC.IncludeType msdElementTypeComplexShape
    End If
    If oSettings.bCellules Then
        oSC.IncludeType msdElementTypeCellHeader
    End If
    If oSettings.bDimensions Then
        oSC.IncludeType msdElementTypeDimension
    End If
    If oSettings.bMultiLignes Then
        oSC.IncludeType msdElementTypeMultiLine
    End If
End Sub

' =============================================================================
' Generation de la signature complete d'un element
' =============================================================================
Private Function GenererSignature(ByVal oElement As Element, _
                                  ByVal oSettings As CSettings) As String
    Dim sSig As String
    Dim sGeo As String
    Dim lVal As Long

    sSig = CStr(oElement.Type) & "|"

    On Error Resume Next

    If oSettings.bComparerNiveau Then
        lVal = -1
        lVal = oElement.Level.Number
        sSig = sSig & CStr(lVal) & "|"
    End If
    If oSettings.bComparerCouleur Then
        lVal = -1
        lVal = oElement.Color
        sSig = sSig & CStr(lVal) & "|"
    End If
    If oSettings.bComparerEpaisseur Then
        lVal = -1
        lVal = oElement.LineWeight
        sSig = sSig & CStr(lVal) & "|"
    End If
    If oSettings.bComparerStyle Then
        lVal = -1
        lVal = oElement.LineStyle.Number
        sSig = sSig & CStr(lVal) & "|"
    End If

    On Error GoTo 0

    sGeo = SignatureGeometrique(oElement)
    If Len(sGeo) = 0 Then
        GenererSignature = ""
    Else
        GenererSignature = sSig & sGeo
    End If
End Function

' =============================================================================
' Dispatch vers la bonne classe de signature selon le type
' =============================================================================
Private Function SignatureGeometrique(ByVal oElement As Element) As String
    Dim s As String
    s = ""

    On Error Resume Next

    Select Case oElement.Type
        Case msdElementTypeLine
            s = m_oSigLigne.SignatureLigne(oElement.AsLineElement)

        Case msdElementTypeLineString
            s = m_oSigLigne.SignatureLineString(oElement.AsLineElement)

        Case msdElementTypePointString
            s = m_oSigLigne.SignaturePointString(oElement.AsLineElement)

        Case msdElementTypeText
            s = m_oSigTexte.SignatureTexte(oElement.AsTextElement)

        Case msdElementTypeTextNode
            s = m_oSigTexte.SignatureTextNode(oElement.AsTextNodeElement)

        Case msdElementTypeArc
            s = m_oSigArc.SignatureArc(oElement.AsArcElement)

        Case msdElementTypeEllipse
            s = m_oSigArc.SignatureEllipse(oElement.AsEllipseElement)

        Case msdElementTypeCurve
            s = m_oSigCourbe.SignatureCurve(oElement.AsCurveElement)

        Case msdElementTypeBsplineCurve
            s = m_oSigCourbe.SignatureBSplineCurve(oElement.AsBsplineCurveElement)

        Case msdElementTypeBsplineSurface
            s = m_oSigCourbe.SignatureBSplineSurface(oElement)

        Case msdElementTypeShape
            s = m_oSigForme.SignatureShape(oElement.AsShapeElement)

        Case msdElementTypeComplexString
            s = m_oSigForme.SignatureComplexString(oElement.AsComplexStringElement)

        Case msdElementTypeComplexShape
            s = m_oSigForme.SignatureComplexShape(oElement.AsComplexShapeElement)

        Case msdElementTypeCellHeader
            s = m_oSigCell.SignatureCell(oElement.AsCellElement)

        Case msdElementTypeDimension
            s = m_oSigCell.SignatureDimension(oElement.AsDimensionElement)

        Case msdElementTypeMultiLine
            s = m_oSigCell.SignatureMultiLine(oElement.AsMultiLineElement)
    End Select

    On Error GoTo 0

    SignatureGeometrique = s
End Function

Attribute VB_Name = "CSettings"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

' =============================================================================
' CSettings - Parametres du nettoyage
' Aucune dependance a l'API MicroStation
' =============================================================================

Public dTolerance       As Double
Public dAngleTolerance  As Double

' --- Types a scanner ---
Public bLignes          As Boolean
Public bTextes          As Boolean
Public bArcs            As Boolean
Public bCourbes         As Boolean
Public bFormes          As Boolean
Public bCellules        As Boolean
Public bDimensions      As Boolean
Public bMultiLignes     As Boolean

' --- Options ---
Public bComparerNiveau      As Boolean
Public bComparerCouleur     As Boolean
Public bComparerEpaisseur   As Boolean
Public bComparerStyle       As Boolean

Sub Init()
    dTolerance = 0.01
    dAngleTolerance = 0.01

    bLignes = True
    bTextes = True
    bArcs = True
    bCourbes = True
    bFormes = True
    bCellules = True
    bDimensions = True
    bMultiLignes = True

    bComparerNiveau = True
    bComparerCouleur = True
    bComparerEpaisseur = True
    bComparerStyle = True
End Sub

Attribute VB_Name = "CSignatureArc"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

' =============================================================================
' CSignatureArc - Calcul de signature pour arcs et ellipses
' Gere : msdElementTypeArc, msdElementTypeEllipse
' Formatage delegue au module partage MFormatSig.
' =============================================================================

Private m_dTol As Double

Sub Init(ByVal dTolerance As Double)
    m_dTol = dTolerance
End Sub

Function SignatureArc(ByVal oArc As ArcElement) As String
    Dim s As String
    s = MFormatSig.FormatPt(oArc.CenterPoint, m_dTol) & "|"
    s = s & MFormatSig.FmtD(oArc.PrimaryRadius, m_dTol) & "|"
    s = s & MFormatSig.FmtD(oArc.SecondaryRadius, m_dTol) & "|"
    s = s & MFormatSig.FmtD(oArc.StartAngle, m_dTol) & "|"
    s = s & MFormatSig.FmtD(oArc.SweepAngle, m_dTol) & "|"
    s = s & MFormatSig.FmtRot(oArc.Rotation, m_dTol)
    SignatureArc = s
End Function

Function SignatureEllipse(ByVal oEllipse As EllipseElement) As String
    Dim s As String
    s = MFormatSig.FormatPt(oEllipse.CenterPoint, m_dTol) & "|"
    s = s & MFormatSig.FmtD(oEllipse.PrimaryRadius, m_dTol) & "|"
    s = s & MFormatSig.FmtD(oEllipse.SecondaryRadius, m_dTol) & "|"
    s = s & MFormatSig.BoolStr(oEllipse.IsFilled)
    SignatureEllipse = s
End Function

Attribute VB_Name = "CSignatureCell"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

' =============================================================================
' CSignatureCell - Calcul de signature pour cellules, dimensions, multilignes
' Gere : msdElementTypeCellHeader, msdElementTypeDimension,
'         msdElementTypeMultiLine
' Formatage delegue au module partage MFormatSig.
' =============================================================================

Private m_dTol As Double

Sub Init(ByVal dTolerance As Double)
    m_dTol = dTolerance
End Sub

Function SignatureCell(ByVal oCell As CellElement) As String
    ' ScaleX/Y/Z n'existent pas : l'echelle est un Point3d (oCell.Scale).
    ' Rotation est une Matrix3d (serialisee par FmtRot, pas traitee en Double).
    Dim s As String
    s = oCell.Name & "|"
    s = s & MFormatSig.FormatPt(oCell.Origin, m_dTol) & "|"
    s = s & MFormatSig.FmtRot(oCell.Rotation, m_dTol) & "|"
    s = s & MFormatSig.FormatPt(oCell.Scale, m_dTol)
    SignatureCell = s
End Function

Function SignatureDimension(ByVal oDim As DimensionElement) As String
    Dim s As String
    Dim oRange As Range3d

    oRange = oDim.Range
    s = MFormatSig.FormatPt(oRange.Low, m_dTol) & "|"
    s = s & MFormatSig.FormatPt(oRange.High, m_dTol) & "|"

    On Error Resume Next
    s = s & oDim.Text
    On Error GoTo 0

    SignatureDimension = s
End Function

Function SignatureMultiLine(ByVal oML As MultiLineElement) As String
    Dim pts() As Point3d
    Dim s As String
    Dim i As Long

    pts = oML.GetVertices
    s = CStr(UBound(pts) - LBound(pts) + 1) & "V|"
    For i = LBound(pts) To UBound(pts)
        s = s & MFormatSig.FormatPt(pts(i), m_dTol) & ";"
    Next i
    s = s & MFormatSig.BoolStr(oML.IsClosed)
    SignatureMultiLine = s
End Function

Attribute VB_Name = "CSignatureCourbe"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

' =============================================================================
' CSignatureCourbe - Calcul de signature pour courbes et B-splines
' Gere : msdElementTypeCurve, msdElementTypeBsplineCurve,
'         msdElementTypeBsplineSurface
' Formatage delegue au module partage MFormatSig.
' =============================================================================

Private m_dTol As Double

Sub Init(ByVal dTolerance As Double)
    m_dTol = dTolerance
End Sub

Function SignatureCurve(ByVal oCurve As CurveElement) As String
    Dim pts() As Point3d
    Dim s As String
    Dim i As Long

    pts = oCurve.GetVertices
    s = CStr(UBound(pts) - LBound(pts) + 1) & "V|"
    For i = LBound(pts) To UBound(pts)
        s = s & MFormatSig.FormatPt(pts(i), m_dTol) & ";"
    Next i
    SignatureCurve = s
End Function

Function SignatureBSplineCurve(ByVal oBSC As BsplineCurveElement) As String
    ' Order/GetPoles/GetKnots sont sur l'objet geometrie BsplineCurve, pas sur
    ' l'element : on l'extrait d'abord. Le flag "closed" n'a pas de propriete
    ' dediee et reste implicite dans les noeuds/poles -> non necessaire ici.
    Dim s As String
    Dim oBc As BsplineCurve
    Dim pts() As Point3d
    Dim knots() As Double
    Dim i As Long

    Set oBc = oBSC.ExtractBsplineCurve

    s = CStr(oBc.Order) & "|"
    pts = oBc.GetPoles
    s = s & CStr(UBound(pts) - LBound(pts) + 1) & "P|"
    For i = LBound(pts) To UBound(pts)
        s = s & MFormatSig.FormatPt(pts(i), m_dTol) & ";"
    Next i

    knots = oBc.GetKnots
    s = s & CStr(UBound(knots) - LBound(knots) + 1) & "K|"
    For i = LBound(knots) To UBound(knots)
        s = s & MFormatSig.FmtD(knots(i), m_dTol) & ";"
    Next i

    SignatureBSplineCurve = s
End Function

Function SignatureBSplineSurface(ByVal oElement As Element) As String
    Dim s As String
    Dim oRange As Range3d

    oRange = oElement.Range
    s = "BSURF|"
    s = s & MFormatSig.FormatPt(oRange.Low, m_dTol) & "|"
    s = s & MFormatSig.FormatPt(oRange.High, m_dTol)
    SignatureBSplineSurface = s
End Function

Attribute VB_Name = "CSignatureForme"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

' =============================================================================
' CSignatureForme - Calcul de signature pour shapes et complex strings/shapes
' Gere : msdElementTypeShape, msdElementTypeComplexString,
'         msdElementTypeComplexShape
' Formatage delegue au module partage MFormatSig.
' =============================================================================

Private m_dTol As Double

Sub Init(ByVal dTolerance As Double)
    m_dTol = dTolerance
End Sub

Function SignatureShape(ByVal oShape As ShapeElement) As String
    Dim pts() As Point3d
    Dim s As String
    Dim i As Long

    pts = oShape.GetVertices
    s = CStr(UBound(pts) - LBound(pts) + 1) & "V|"
    s = s & MFormatSig.BoolStr(oShape.IsFilled) & "|"
    For i = LBound(pts) To UBound(pts)
        s = s & MFormatSig.FormatPt(pts(i), m_dTol) & ";"
    Next i
    SignatureShape = s
End Function

Function SignatureComplexString(ByVal oComplex As ComplexStringElement) As String
    Dim s As String
    Dim oEnum As ElementEnumerator
    Dim oSub As Element
    Dim lCount As Long

    s = ""
    lCount = 0
    Set oEnum = oComplex.GetSubElements

    Do While oEnum.MoveNext
        Set oSub = oEnum.Current
        lCount = lCount + 1
        s = s & SignatureSousElement(oSub) & "#"
    Loop

    SignatureComplexString = CStr(lCount) & "S|" & s
End Function

Function SignatureComplexShape(ByVal oComplex As ComplexShapeElement) As String
    Dim s As String
    Dim oEnum As ElementEnumerator
    Dim oSub As Element
    Dim lCount As Long

    s = ""
    lCount = 0
    Set oEnum = oComplex.GetSubElements

    Do While oEnum.MoveNext
        Set oSub = oEnum.Current
        lCount = lCount + 1
        s = s & SignatureSousElement(oSub) & "#"
    Loop

    SignatureComplexShape = MFormatSig.BoolStr(oComplex.IsFilled) & "|" & CStr(lCount) & "S|" & s
End Function

' --- Signature simplifiee d'un sous-element (sans recurse infinie) ---
Private Function SignatureSousElement(ByVal oSub As Element) As String
    Dim s As String
    Dim oRange As Range3d

    s = CStr(oSub.Type) & ":"
    oRange = oSub.Range
    s = s & MFormatSig.FormatPt(oRange.Low, m_dTol) & ">" & MFormatSig.FormatPt(oRange.High, m_dTol)
    SignatureSousElement = s
End Function

Attribute VB_Name = "CSignatureLigne"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

' =============================================================================
' CSignatureLigne - Calcul de signature pour lignes et linestrings
' Gere : msdElementTypeLine, msdElementTypeLineString, msdElementTypePointString
' Formatage delegue au module partage MFormatSig.
' =============================================================================

Private m_dTol As Double

Sub Init(ByVal dTolerance As Double)
    m_dTol = dTolerance
End Sub

Function SignatureLigne(ByVal oLine As LineElement) As String
    ' StartPoint/EndPoint sont propres a ArcElement : sur une ligne on prend les
    ' extremites via GetVertices (voie confirmee).
    Dim pts() As Point3d
    pts = oLine.GetVertices
    SignatureLigne = MFormatSig.FormatPt(pts(LBound(pts)), m_dTol) & ">" & _
                     MFormatSig.FormatPt(pts(UBound(pts)), m_dTol)
End Function

Function SignatureLineString(ByVal oLine As LineElement) As String
    Dim pts() As Point3d
    Dim s As String
    Dim i As Long

    pts = oLine.GetVertices
    s = CStr(UBound(pts) - LBound(pts) + 1) & "V|"
    For i = LBound(pts) To UBound(pts)
        s = s & MFormatSig.FormatPt(pts(i), m_dTol) & ";"
    Next i
    SignatureLineString = s
End Function

Function SignaturePointString(ByVal oLine As LineElement) As String
    SignaturePointString = SignatureLineString(oLine)
End Function

Attribute VB_Name = "CSignatureTexte"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

' =============================================================================
' CSignatureTexte - Calcul de signature pour textes et text nodes
' Gere : msdElementTypeText, msdElementTypeTextNode
' Formatage delegue au module partage MFormatSig.
' =============================================================================

Private m_dTol As Double

Sub Init(ByVal dTolerance As Double)
    m_dTol = dTolerance
End Sub

Function SignatureTexte(ByVal oText As TextElement) As String
    Dim s As String
    s = oText.Text & "|"
    s = s & MFormatSig.FormatPt(oText.Origin, m_dTol) & "|"
    s = s & MFormatSig.FmtD(oText.TextStyle.Height, m_dTol) & "|"
    s = s & MFormatSig.FmtD(oText.TextStyle.Width, m_dTol) & "|"
    s = s & CStr(oText.TextStyle.Font.ID)
    SignatureTexte = s
End Function

Function SignatureTextNode(ByVal oNode As TextNodeElement) As String
    ' Un TextNode n'expose pas .Text ni .TextStyle : ils vivent sur les
    ' TextElement enfants (chaque ligne a son propre style). On itere donc les
    ' sous-elements et on integre texte + style de CHAQUE ligne a la signature.
    Dim s As String
    Dim ee As ElementEnumerator
    Dim oLigne As TextElement

    s = MFormatSig.FormatPt(oNode.Origin, m_dTol) & "|"
    s = s & CStr(oNode.TextLinesCount) & "|"

    Set ee = oNode.GetSubElements
    Do While ee.MoveNext
        If ee.Current.IsTextElement Then
            Set oLigne = ee.Current
            s = s & oLigne.Text & "~"
            s = s & MFormatSig.FmtD(oLigne.TextStyle.Height, m_dTol) & "~"
            s = s & MFormatSig.FmtD(oLigne.TextStyle.Width, m_dTol) & "~"
            s = s & CStr(oLigne.TextStyle.Font.ID) & ";"
        End If
    Loop

    SignatureTextNode = s
End Function

Attribute VB_Name = "MFormatSig"
Option Explicit

' =============================================================================
' MFormatSig - Fonctions de formatage partagees par les classes CSignature*
'
' Regroupe FmtD / FormatPt / BoolStr, jusqu'ici copiees a l'identique dans les
' six classes de signature. La tolerance de quantification est passee en
' parametre (elle est commune a un scan : CSettings.dTolerance). Fonctions pures,
' sans etat.
' =============================================================================

' Quantifie d sur la grille de pas dTol, formate a 4 decimales.
Public Function FmtD(ByVal d As Double, ByVal dTol As Double) As String
    FmtD = Format$(Round(d / dTol) * dTol, "0.0000")
End Function

' Formate un point (X,Y,Z) quantifie.
Public Function FormatPt(ByRef pt As Point3d, ByVal dTol As Double) As String
    FormatPt = FmtD(pt.X, dTol) & "," & FmtD(pt.Y, dTol) & "," & FmtD(pt.Z, dTol)
End Function

' "T" / "F" pour un booleen.
Public Function BoolStr(ByVal b As Boolean) As String
    If b Then BoolStr = "T" Else BoolStr = "F"
End Function

' Serialise une rotation (Matrix3d) par ses vecteurs RowX et RowY quantifies.
' Deux orientations identiques -> meme chaine ; suffit a la deduplication et
' evite de traiter la Matrix3d comme un scalaire (piege corrige).
Public Function FmtRot(ByRef rot As Matrix3d, ByVal dTol As Double) As String
    FmtRot = FmtD(rot.RowX.X, dTol) & "," & FmtD(rot.RowX.Y, dTol) & "," & _
             FmtD(rot.RowX.Z, dTol) & "," & _
             FmtD(rot.RowY.X, dTol) & "," & FmtD(rot.RowY.Y, dTol) & "," & _
             FmtD(rot.RowY.Z, dTol)
End Function

Attribute VB_Name = "NettoyageDoublonsV1"
Option Explicit

' =============================================================================
' NettoyageDoublonsV1 - Suppression des elements en doublon dans un DGN
' MicroStation V8i SS3 - VBA 6.x
' Ne prend pas en compte les fichiers en reference
' =============================================================================

' --- Globals partages ---
Public g_oSettings      As CSettings
Public g_oMoteur        As CMoteurScan

'----------------------------------------------------------------------
Sub NettoyageDoublons()
    Dim oDgn As DesignFile
    On Error Resume Next
    Set oDgn = ActiveDesignFile
    On Error GoTo 0
    If oDgn Is Nothing Then
        MsgBox "Ouvrez d'abord un fichier DGN.", vbExclamation, "Nettoyage Doublons"
        Exit Sub
    End If

    Set g_oSettings = New CSettings
    g_oSettings.Init

    Set g_oMoteur = New CMoteurScan

    frmNettoyage.Initialiser g_oSettings
    frmNettoyage.Show vbModeless
End Sub

'----------------------------------------------------------------------
Sub LancerAnalyse()
    If g_oMoteur Is Nothing Then Exit Sub

    If g_oMoteur.NbDoublonsTrouves > 0 Then
        g_oMoteur.EffacerSurbrillance ActiveModelReference
    End If

    g_oMoteur.Analyser ActiveModelReference, g_oSettings

    If g_oMoteur.NbDoublonsTrouves > 0 Then
        g_oMoteur.SurlignierDoublons ActiveModelReference
    End If
    frmNettoyage.AfficherResultat g_oMoteur.NbElementsScannes, _
                                  g_oMoteur.NbDoublonsTrouves
End Sub

'----------------------------------------------------------------------
Sub LancerSuppression()
    If g_oMoteur Is Nothing Then Exit Sub
    If g_oMoteur.NbDoublonsTrouves = 0 Then Exit Sub
    g_oMoteur.EffacerSurbrillance ActiveModelReference
    g_oMoteur.SupprimerDoublons ActiveModelReference
    frmNettoyage.AfficherSuppression g_oMoteur.NbSupprimes
End Sub

'----------------------------------------------------------------------
Sub NettoyerAvantFermeture()
    If g_oMoteur Is Nothing Then Exit Sub
    g_oMoteur.EffacerSurbrillance ActiveModelReference
End Sub

Attribute VB_Name = "frmNettoyage"
Attribute VB_Base = "0{06F0AA56-82E4-48DC-8E48-A478C5F56A37}{4884C6D8-42F6-4964-9321-1044D9FF9DA4}"
Attribute VB_GlobalNameSpace = False
Attribute VB_Creatable = False
Attribute VB_PredeclaredId = True
Attribute VB_Exposed = False
Attribute VB_TemplateDerived = False
Attribute VB_Customizable = False

Option Explicit

' =============================================================================
' frmNettoyage - Formulaire modeless pour le nettoyage des doublons
' Controles crees au runtime dans ConstruireControles
' =============================================================================

Private m_bConstruit    As Boolean
Private m_bInit         As Boolean
Private m_oSettings     As CSettings

' --- Controles declares WithEvents pour recevoir les evenements ---
Private WithEvents chkLignes        As MSForms.CheckBox
Attribute chkLignes.VB_VarHelpID = -1
Private WithEvents chkTextes        As MSForms.CheckBox
Attribute chkTextes.VB_VarHelpID = -1
Private WithEvents chkArcs          As MSForms.CheckBox
Attribute chkArcs.VB_VarHelpID = -1
Private WithEvents chkCourbes       As MSForms.CheckBox
Attribute chkCourbes.VB_VarHelpID = -1
Private WithEvents chkFormes        As MSForms.CheckBox
Attribute chkFormes.VB_VarHelpID = -1
Private WithEvents chkCellules      As MSForms.CheckBox
Attribute chkCellules.VB_VarHelpID = -1
Private WithEvents chkDimensions    As MSForms.CheckBox
Attribute chkDimensions.VB_VarHelpID = -1
Private WithEvents chkMultiLignes   As MSForms.CheckBox
Attribute chkMultiLignes.VB_VarHelpID = -1

Private WithEvents chkNiveau        As MSForms.CheckBox
Attribute chkNiveau.VB_VarHelpID = -1
Private WithEvents chkCouleur       As MSForms.CheckBox
Attribute chkCouleur.VB_VarHelpID = -1
Private WithEvents chkEpaisseur     As MSForms.CheckBox
Attribute chkEpaisseur.VB_VarHelpID = -1
Private WithEvents chkStyle         As MSForms.CheckBox
Attribute chkStyle.VB_VarHelpID = -1

Private WithEvents btnAnalyser      As MSForms.CommandButton
Attribute btnAnalyser.VB_VarHelpID = -1
Private WithEvents btnSupprimer     As MSForms.CommandButton
Attribute btnSupprimer.VB_VarHelpID = -1
Private WithEvents btnFermer        As MSForms.CommandButton
Attribute btnFermer.VB_VarHelpID = -1

Private WithEvents txtTolerance     As MSForms.TextBox
Attribute txtTolerance.VB_VarHelpID = -1
Private WithEvents txtAngleTol      As MSForms.TextBox
Attribute txtAngleTol.VB_VarHelpID = -1

Private lblResultat                 As MSForms.Label
Private lblStatus                   As MSForms.Label

' =============================================================================
Private Sub UserForm_Initialize()
    If Not m_bConstruit Then ConstruireControles
End Sub

' =============================================================================
Public Sub Initialiser(ByVal oSettings As CSettings)
    m_bInit = True
    Set m_oSettings = oSettings

    If Not m_bConstruit Then ConstruireControles

    chkLignes.Value = oSettings.bLignes
    chkTextes.Value = oSettings.bTextes
    chkArcs.Value = oSettings.bArcs
    chkCourbes.Value = oSettings.bCourbes
    chkFormes.Value = oSettings.bFormes
    chkCellules.Value = oSettings.bCellules
    chkDimensions.Value = oSettings.bDimensions
    chkMultiLignes.Value = oSettings.bMultiLignes

    chkNiveau.Value = oSettings.bComparerNiveau
    chkCouleur.Value = oSettings.bComparerCouleur
    chkEpaisseur.Value = oSettings.bComparerEpaisseur
    chkStyle.Value = oSettings.bComparerStyle

    txtTolerance.Text = Format$(oSettings.dTolerance, "0.0000")
    txtAngleTol.Text = Format$(oSettings.dAngleTolerance, "0.0000")

    lblResultat.Caption = ""
    lblStatus.Caption = "Pret."
    btnSupprimer.Enabled = False

    m_bInit = False
End Sub

' =============================================================================
Public Sub AfficherResultat(ByVal lScannes As Long, ByVal lDoublons As Long)
    lblResultat.Caption = "Scannes: " & lScannes & vbCrLf & _
                          "Doublons: " & lDoublons
    If lDoublons > 0 Then
        btnSupprimer.Enabled = True
        lblStatus.Caption = lDoublons & " doublons prets a supprimer."
    Else
        btnSupprimer.Enabled = False
        lblStatus.Caption = "Aucun doublon trouve."
    End If
End Sub

' =============================================================================
Public Sub AfficherSuppression(ByVal lSupprimes As Long)
    lblStatus.Caption = lSupprimes & " doublons supprimes."
    lblResultat.Caption = lblResultat.Caption & vbCrLf & _
                          "Supprimes: " & lSupprimes
    btnSupprimer.Enabled = False
End Sub

' =============================================================================
Private Sub ConstruireControles()
    Dim fraTypes As MSForms.Frame
    Dim fraOptions As MSForms.Frame
    Dim fraActions As MSForms.Frame
    Dim nTop As Long

    Me.Width = 240
    Me.Height = 430

    ' --- Frame : Types d'elements ---
    Set fraTypes = Me.Controls.Add("Forms.Frame.1", "fraTypes")
    fraTypes.Caption = "Types a scanner"
    fraTypes.Left = 6: fraTypes.Top = 6: fraTypes.Width = 222: fraTypes.Height = 138

    nTop = 14
    Set chkLignes = fraTypes.Controls.Add("Forms.CheckBox.1", "chkLignes")
    chkLignes.Caption = "Lignes / LineStrings"
    chkLignes.Left = 8: chkLignes.Top = nTop: chkLignes.Width = 140: chkLignes.Height = 14
    nTop = nTop + 14

    Set chkTextes = fraTypes.Controls.Add("Forms.CheckBox.1", "chkTextes")
    chkTextes.Caption = "Textes / TextNodes"
    chkTextes.Left = 8: chkTextes.Top = nTop: chkTextes.Width = 140: chkTextes.Height = 14
    nTop = nTop + 14

    Set chkArcs = fraTypes.Controls.Add("Forms.CheckBox.1", "chkArcs")
    chkArcs.Caption = "Arcs / Ellipses"
    chkArcs.Left = 8: chkArcs.Top = nTop: chkArcs.Width = 140: chkArcs.Height = 14
    nTop = nTop + 14

    Set chkCourbes = fraTypes.Controls.Add("Forms.CheckBox.1", "chkCourbes")
    chkCourbes.Caption = "Courbes / B-Splines"
    chkCourbes.Left = 8: chkCourbes.Top = nTop: chkCourbes.Width = 140: chkCourbes.Height = 14
    nTop = nTop + 14

    Set chkFormes = fraTypes.Controls.Add("Forms.CheckBox.1", "chkFormes")
    chkFormes.Caption = "Shapes / Complex"
    chkFormes.Left = 8: chkFormes.Top = nTop: chkFormes.Width = 140: chkFormes.Height = 14
    nTop = nTop + 14

    Set chkCellules = fraTypes.Controls.Add("Forms.CheckBox.1", "chkCellules")
    chkCellules.Caption = "Cellules"
    chkCellules.Left = 8: chkCellules.Top = nTop: chkCellules.Width = 140: chkCellules.Height = 14
    nTop = nTop + 14

    Set chkDimensions = fraTypes.Controls.Add("Forms.CheckBox.1", "chkDimensions")
    chkDimensions.Caption = "Dimensions"
    chkDimensions.Left = 8: chkDimensions.Top = nTop: chkDimensions.Width = 140: chkDimensions.Height = 14
    nTop = nTop + 14

    Set chkMultiLignes = fraTypes.Controls.Add("Forms.CheckBox.1", "chkMultiLignes")
    chkMultiLignes.Caption = "MultiLignes"
    chkMultiLignes.Left = 8: chkMultiLignes.Top = nTop: chkMultiLignes.Width = 140: chkMultiLignes.Height = 14

    ' --- Frame : Criteres de comparaison ---
    Set fraOptions = Me.Controls.Add("Forms.Frame.1", "fraOptions")
    fraOptions.Caption = "Criteres de comparaison"
    fraOptions.Left = 6: fraOptions.Top = 148: fraOptions.Width = 222: fraOptions.Height = 126

    nTop = 14
    Set chkNiveau = fraOptions.Controls.Add("Forms.CheckBox.1", "chkNiveau")
    chkNiveau.Caption = "Niveau (Level)"
    chkNiveau.Left = 8: chkNiveau.Top = nTop: chkNiveau.Width = 100: chkNiveau.Height = 14

    Set chkCouleur = fraOptions.Controls.Add("Forms.CheckBox.1", "chkCouleur")
    chkCouleur.Caption = "Couleur"
    chkCouleur.Left = 112: chkCouleur.Top = nTop: chkCouleur.Width = 100: chkCouleur.Height = 14
    nTop = nTop + 14

    Set chkEpaisseur = fraOptions.Controls.Add("Forms.CheckBox.1", "chkEpaisseur")
    chkEpaisseur.Caption = "Epaisseur"
    chkEpaisseur.Left = 8: chkEpaisseur.Top = nTop: chkEpaisseur.Width = 100: chkEpaisseur.Height = 14

    Set chkStyle = fraOptions.Controls.Add("Forms.CheckBox.1", "chkStyle")
    chkStyle.Caption = "Style"
    chkStyle.Left = 112: chkStyle.Top = nTop: chkStyle.Width = 100: chkStyle.Height = 14
    nTop = nTop + 20

    Dim lblTol As MSForms.Label
    Set lblTol = fraOptions.Controls.Add("Forms.Label.1", "lblTol")
    lblTol.Caption = "Tol. distance :"
    lblTol.Left = 8: lblTol.Top = nTop + 2: lblTol.Width = 80: lblTol.Height = 14

    Set txtTolerance = fraOptions.Controls.Add("Forms.TextBox.1", "txtTolerance")
    txtTolerance.Left = 92: txtTolerance.Top = nTop: txtTolerance.Width = 60: txtTolerance.Height = 18
    nTop = nTop + 22

    Dim lblAngTol As MSForms.Label
    Set lblAngTol = fraOptions.Controls.Add("Forms.Label.1", "lblAngTol")
    lblAngTol.Caption = "Tol. angle :"
    lblAngTol.Left = 8: lblAngTol.Top = nTop + 2: lblAngTol.Width = 80: lblAngTol.Height = 14

    Set txtAngleTol = fraOptions.Controls.Add("Forms.TextBox.1", "txtAngleTol")
    txtAngleTol.Left = 92: txtAngleTol.Top = nTop: txtAngleTol.Width = 60: txtAngleTol.Height = 18

    ' --- Frame : Actions ---
    Set fraActions = Me.Controls.Add("Forms.Frame.1", "fraActions")
    fraActions.Caption = "Actions"
    fraActions.Left = 6: fraActions.Top = 278: fraActions.Width = 222: fraActions.Height = 98

    Set btnAnalyser = fraActions.Controls.Add("Forms.CommandButton.1", "btnAnalyser")
    btnAnalyser.Caption = "Analyser"
    btnAnalyser.Left = 8: btnAnalyser.Top = 16: btnAnalyser.Width = 80: btnAnalyser.Height = 22

    Set btnSupprimer = fraActions.Controls.Add("Forms.CommandButton.1", "btnSupprimer")
    btnSupprimer.Caption = "Supprimer"
    btnSupprimer.Left = 96: btnSupprimer.Top = 16: btnSupprimer.Width = 80: btnSupprimer.Height = 22
    btnSupprimer.Enabled = False

    Set lblResultat = fraActions.Controls.Add("Forms.Label.1", "lblResultat")
    lblResultat.Caption = ""
    lblResultat.Left = 8: lblResultat.Top = 44: lblResultat.Width = 200: lblResultat.Height = 40
    lblResultat.WordWrap = True

    ' --- Barre de statut en bas ---
    Set lblStatus = Me.Controls.Add("Forms.Label.1", "lblStatus")
    lblStatus.Caption = "Pret."
    lblStatus.Left = 6: lblStatus.Top = 382: lblStatus.Width = 222: lblStatus.Height = 14

    ' --- Bouton Fermer ---
    Set btnFermer = Me.Controls.Add("Forms.CommandButton.1", "btnFermer")
    btnFermer.Caption = "Fermer"
    btnFermer.Left = 150: btnFermer.Top = 382: btnFermer.Width = 78: btnFermer.Height = 20

    m_bConstruit = True
End Sub

' =============================================================================
' Evenements des checkboxes - Types
' =============================================================================
Private Sub chkLignes_Click()
    If m_bInit Then Exit Sub
    m_oSettings.bLignes = chkLignes.Value
End Sub

Private Sub chkTextes_Click()
    If m_bInit Then Exit Sub
    m_oSettings.bTextes = chkTextes.Value
End Sub

Private Sub chkArcs_Click()
    If m_bInit Then Exit Sub
    m_oSettings.bArcs = chkArcs.Value
End Sub

Private Sub chkCourbes_Click()
    If m_bInit Then Exit Sub
    m_oSettings.bCourbes = chkCourbes.Value
End Sub

Private Sub chkFormes_Click()
    If m_bInit Then Exit Sub
    m_oSettings.bFormes = chkFormes.Value
End Sub

Private Sub chkCellules_Click()
    If m_bInit Then Exit Sub
    m_oSettings.bCellules = chkCellules.Value
End Sub

Private Sub chkDimensions_Click()
    If m_bInit Then Exit Sub
    m_oSettings.bDimensions = chkDimensions.Value
End Sub

Private Sub chkMultiLignes_Click()
    If m_bInit Then Exit Sub
    m_oSettings.bMultiLignes = chkMultiLignes.Value
End Sub

' =============================================================================
' Evenements des checkboxes - Criteres
' =============================================================================
Private Sub chkNiveau_Click()
    If m_bInit Then Exit Sub
    m_oSettings.bComparerNiveau = chkNiveau.Value
End Sub

Private Sub chkCouleur_Click()
    If m_bInit Then Exit Sub
    m_oSettings.bComparerCouleur = chkCouleur.Value
End Sub

Private Sub chkEpaisseur_Click()
    If m_bInit Then Exit Sub
    m_oSettings.bComparerEpaisseur = chkEpaisseur.Value
End Sub

Private Sub chkStyle_Click()
    If m_bInit Then Exit Sub
    m_oSettings.bComparerStyle = chkStyle.Value
End Sub

' =============================================================================
' Evenements des TextBox - Tolerances
' =============================================================================
Private Sub txtTolerance_Change()
    If m_bInit Then Exit Sub
    Dim d As Double
    If IsNumeric(txtTolerance.Text) Then
        d = CDbl(txtTolerance.Text)
        If d > 0 Then m_oSettings.dTolerance = d
    End If
End Sub

Private Sub txtTolerance_KeyDown(ByVal KeyCode As MSForms.ReturnInteger, ByVal Shift As Integer)
    If KeyCode = vbKeyReturn Then
        txtTolerance.Text = Format$(m_oSettings.dTolerance, "0.0000")
    End If
End Sub

Private Sub txtAngleTol_Change()
    If m_bInit Then Exit Sub
    Dim d As Double
    If IsNumeric(txtAngleTol.Text) Then
        d = CDbl(txtAngleTol.Text)
        If d > 0 Then m_oSettings.dAngleTolerance = d
    End If
End Sub

Private Sub txtAngleTol_KeyDown(ByVal KeyCode As MSForms.ReturnInteger, ByVal Shift As Integer)
    If KeyCode = vbKeyReturn Then
        txtAngleTol.Text = Format$(m_oSettings.dAngleTolerance, "0.0000")
    End If
End Sub

' =============================================================================
' Boutons d'action
' =============================================================================
Private Sub btnAnalyser_Click()
    btnAnalyser.Enabled = False
    lblStatus.Caption = "Analyse en cours..."
    lblResultat.Caption = ""
    btnSupprimer.Enabled = False
    DoEvents
    LancerAnalyse
    btnAnalyser.Enabled = True
End Sub

Private Sub btnSupprimer_Click()
    Dim rep As VbMsgBoxResult
    rep = MsgBox("Confirmer la suppression des doublons ?", _
                 vbYesNo + vbQuestion, "Nettoyage Doublons")
    If rep = vbYes Then
        lblStatus.Caption = "Suppression en cours..."
        DoEvents
        LancerSuppression
    End If
End Sub

Private Sub btnFermer_Click()
    NettoyerAvantFermeture
    Me.Hide
    CommandState.StartDefaultCommand
End Sub

' =============================================================================
' Fermeture par la croix
' =============================================================================
Private Sub UserForm_QueryClose(Cancel As Integer, CloseMode As Integer)
    If CloseMode = vbFormControlMenu Then
        Cancel = 1
        NettoyerAvantFermeture
        Me.Hide
        CommandState.StartDefaultCommand
    End If
End Sub
